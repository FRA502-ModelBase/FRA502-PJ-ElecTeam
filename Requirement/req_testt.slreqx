# req_testt

## R1: Emergency status (Functional)
Battery emergency status

### R1.1: Emer battery False (Functional)
Automatic emergency is enabling (batteryOk=false) when one or more of the following are met:
* Battery temperature (battery_temp>=x)
* Battery Current (A) (battery_current>=y)
* Voltage Level (V) (battery_voltage> =z)

#### R1.1.1: battery_temp (Functional)
Automatic emergency is enabling (batteryOk=false)this condition are met Battery temperature (battery_temp>=x):

#### R1.1.2: battery_current (Functional)
Automatic emergency is enabling (batteryOk=false)this condition are met Battery temperature (battery_current>=x):

#### R1.1.3: battery_voltage (Functional)
Automatic emergency is enabling (batteryOk=false)this condition are met Battery temperature (battery_voltage>=x):

### R1.2: Emer battery True (Functional)
Automatic emergency is enabling (batteryOk=True) when one or more of the following are met:
* Battery temperature (battery_temp<=x)
* Battery Current (A) (battery_current<=y)
* Voltage Level (V) (battery_voltage<=z)
