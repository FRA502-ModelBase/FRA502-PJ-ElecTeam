# req_testt

## R1: Monitorability (Functional)

### R1.1: System Current (Functional)
หุ่นยนต์จะต้องมีอุปกรณ์หรือระบบในการตรวจสอบการปริมาณกระเเสไฟฟ้าที่หุ่นยนต์ใช้งานโดยเก็บข้อมูลไว้ที่
- Sys_Amp
- Rationale: เพื่อตวจสอบการทำงานของอุปกรณ์ไฟฟ้าต่างๆ ป้องกันการทำงานที่เกินกระเเสพิกัดของหุ่นยนต์เเละตรวจสอบการใช้พลังงานของหุ่นยนต์

### R1.2: System Voltage (Functional)
หุ่นยนต์จะต้องมีอุปกรณ์หรือระบบในการตรวจสอบความต่างศักย์ของหุ่นยนต์โดยเก็บค่าไว้ที่
- Sys_Volt
- Rationale: เพื่อรับรู้สถานะของความต่างศักย์ในระบบต่างๆของหุ่ยนต์เพื่อใช้ตรวจสอบการทำงานของระบบไฟฟ้าต่างๆ

### R1.3: Battery Temperature (Functional)
หุ่นยนต์จะต้องมีอุปกรณ์หรือระบบในการตรวจสอบอุณหภูมิของเเบตเตอรี่โดยเก็บข้อมูลไว้ที่
- Batt_Temp
- Rationale: ป้องกันความเสียหายที่อาจเกิดขึ้นเนื่องจากความร้อนที่มากเกินไปของเเบตเตอรี่

### R1.4: Battery Level (Functional)
หุ่นยนต์จะต้องมีอุปกรณ์หรือระบบในการตรวจสอบระดับพลังงานที่เหลืออยู่ภายในเเบตเตอรี่โดยเก็บข้อมูลไว้ที่
- Batt_Level
- Rationale: ติดตามระดับพลังงานของเเบตเตอรี่ให้อยู่ในระดับที่เหมาะสม

## R2: Internal Power Limitation (Functional)

### R2.1: System Over Current (Functional)
ตรวจพบการใช้งานกระเเสไฟฟ้ามากกว่าที่กำหนด (Over_Amp_Stat = True) เมื่อเกิดสภาวะการดังนี้
- Sys_Amp >= Max_Sys_Amp
- Rationale: เพื่อป้องกันความเสียหายของเเหล่งจ่ายไฟเนื่องจากการลัดวงจรหรือการใช้งานเกินกระเเสพิกัดของระบบ

### R2.2: System Under Voltage (Functional)
ตรวจพบความต่างศักย์ต่ำกว่าค่าที่กำหนด (Under_Volt_Stat = True) เมื่อเกิดสภาวะการดังนี้
- Sys_Volt < Min_Sys_Volt
- Rationale: เพื่อป้องกันความเสียหายของเเบตเตอรี่จากการ Over Discharge

### R2.3: Maximum System Voltage (Functional)
ตรวจพบความต่างศักย์สูงกว่าค่าที่กำหนด (Over_Volt_Stat = True) เมื่อเกิดสภาวะการดังนี้
- Sys_Volt > Max_Sys_Volt
- Rationale: เพื่อป้องกันความเสียหายของอุปกรณ์ไฟฟ้าต่างๆ จากความต่างศักย์ที่มากเกินกว่าที่กำหนด

### R2.4: Normally System Voltage (Functional)
ความต่างศักย์ของระบบอยู่ระหว่างค่าที่กำหนด (Over_Volt_Stat = False , Under_Volt_Stat = False)
- Sys_Volt >= Min_Sys_Volt
- Sys_Volt <= Max_Sys_Volt
- Rationale: ใช้ควบคุมการจ่ายไฟฟ้าให้อุปกรณ์ต่างๆเมื่ออยู่ในสถานะการที่เหมาะสม

## R3: Rechargeability (Functional)

### R3.1: Battery Life Time (Functional)
เเบตเตอรี่ต้องมีอายุการใช้งานอย่างต่อเนื่องต่อหนึ่งรอบการชาร์ตไม่น้อยกว่าระยะเวลาที่กำหนด
- Batt_Life_Time >= ระยะเวลาการทำงานต่อหนึ่งรอบการชาร์จ

### R3.3: Battery Over Temperature while Charging (Functional)
อุณหภูมิของเเบตเตอรี่ขณะทำการชาร์ตสูงเกินค่าที่กำหนด (Batt_Charge_Over_Temp = True) เมื่อเกิดสภาวะการดังนี้
- Batt_Temp >= Max_Batt_Temp
- Batt_Charging_Stat == True
- Rationale: ใช้หยุดทำการชาร์ตเเบตเตอรี่เมื่ออุณหภูมิขณะชาร์ตเเบตเตอรี่สูงเกินค่าที่กำหนด

### R3.4: Battery Low Level (Functional)
ระดับพลังงานของเเบตเตอรี่ต่ำกว่าค่าที่กำหนด (Batt_Low_Stat = True) เมื่อเกิดสภาวะดังนี้
- Batt_Percent <= Min_Batt
- Rationale: ระบบจัดการพลังงานมีข้อมูลในการสั่งให้หุ่นยนต์กลับไปชาร์จเเบต

### R3.5: Start to Charge at the Charging Station (Functional)
เริ่มต้นการชาร์จเเบตเตอรี่ (Batt_Charging_Stat = True) เมื่อเกิดสภาวะดังต่อไปนี้ครบทุกข้อ
- Batt_Low_Stat = True
- Robot_with_Charger_Stat = True
- Batt_Charge_Over_Temp = Flase

### R3.6: Stop to Charge at the Charging Station (Functional)
หยุดการชาร์ตเเบตเตอรี่ (Batt_Charging_Stat = False เเละ Batt_Low_Stat = False) เมื่อเกิดสภาวะดังต่อไปนี้ข้อใดข้อหนึ่ง
(Batt_Charge_Over_Temp = True)
(Robot_with_Charger_Stat = False)
(Batt_Percent = 100%)

#### R3.6.1: stop to charge when battery over temperature while charging (Functional)
หยุดการชาร์ตเเบตเตอรี่ (Batt_Charging_Stat = False เเละ Batt_Low_Stat = False) เมื่อเกิดสภาวะดังต่อไป
- Batt_Charge_Over_Temp == True

#### R3.6.2: stop charg when robot is not with charger (Functional)
หยุดการชาร์ตเเบตเตอรี่ (Batt_Charging_Stat = False เเละ Batt_Low_Stat = False) เมื่อเกิดสภาวะดังต่อไปนี้
- Robot_with_Charger_Stat == False

#### R3.6.3: stop to charge when battery percentage is 100% (Functional)
หยุดการชาร์ตเเบตเตอรี่ (Batt_Charging_Stat = False เเละ Batt_Low_Stat = False) เมื่อเกิดสภาวะดังต่อไปนี้
- Batt_Percent == 100%

### R3.2: Battery Charge Time (Functional)
เเบตเตอรี่ต้องสามารถชาร์ตเเบตเตอรี่จาก 0-100% (SOC) ได้ภายในระยะเวลาที่กำหนด
- Batt_Charge_Time >= เวลาที่ใช้ในการชาร์จ

## R4: Emergency Trigger Behavior (Functional)

### R4.1: Environment Temperature Warning (both over and under) (Functional)
เพื่อให้ระบบสามารถตอบสนองกับอุณภูมิ ณ ปัจจุบันได้ เช่น กลับไปจุดที่มีอุณหภูมิต่ำลง หรือปิดการทำงาน

#### R4.1.1: Over Temperature Level (Functional)
เมื่ออุณหภูมิสภาพเเวดล้อมเกินอุณหภูมิที่กำหนดไว้ ระบบจะมีการเตือน ( Over_Temp_Stat = true ) เมื่อมีค่าตามเงื่อนไขดังนี้
- Current_Env_Temp >= Max_Env_Temp_Threshold

#### R4.1.2: Under Temperature Level (Functional)
เมื่ออุณหภูมิสภาพเเวดล้อมต่ำกว่าอุณหภูมิที่กำหนดไว้ ระบบจะมีการเตือน ( Under_Temp_Stat = true) เมื่อมีค่าตามเงื่อนไขดังนี้
- Current_Env_Temp <= Min_Env_Temp_Threshold

#### R4.1.3: Normal Operating Temperature Level (Functional)
เมื่ออุณหภูมิสภาพเเวดล้อมอยู่ในช่วงที่กำหนด สถานะเตือนอุณหภูมิจะกลับมามี สถาณะเดิม หรือ false ( stat_under_temp = false และ stat_over_temp = false)
- Current_Env_Temp <= Max_Env_Temp_Threshold
- Current_Env_Temp > Min_Env_Temp_Threshold

### R4.2: Collision Detection (Functional)

#### R4.2.1: Collision Warning (Functional)
เมื่อหุ่นยนต์พบเจอสิ่งกีดขวางผ่านเซ็นเซอร์ ระบบจะส่งคำเตือนการเจอสิ่งกีดขวางไปยังระบบนำทางเพื่อประมวลผลเส้นทางใหม่ (Collision_Flag = true) จนกว่าระบบจะมีการรับรู้ เมื่อมีค่าตามเงื่อนไขดังนี้
- Collision_In == true

#### R4.2.2: Collision Acknowledging (Functional)
เมื่อระบบนำทางได้ตอบสนองกลับมาคำเตือนการเจอสิ่งกีดขวางจะกลับสู่สถาณะเดิม หรือ false (Collision_Flag = false) เมื่อมีค่าตามเงื่อนไขดังนี้
- Collision_Ack == true

### R4.3: Embedded devices status (Functional)

#### R4.3.1: Electronic Devices Timeout (Functional)
เมื่อหุ่นยนต์พบว่ามีอุปกรณ์ที่หยุดการทำงาน (ไม่ส่งสถาณะกลับมาที่ระบบเฝ้าระวัง) หุ่นยนต์จะมีการเตือนสถาณะอุปกรณ์เพื่อให้ระบบเข้าสู้สถานะฉุกเฉินได้(Device_Fail_Stat = true) และส่งคำสั่งเริ่มต้นใหม่ไปยังอุปกรณ์ (Reset_Trig = true) เมื่อมีค่าตามเงื่อนไขดังนี้
- Last_Hearhbeat_Time - Current_Time > Heartbeat_Time_Threshold

#### R4.3.2: Electronic Devices Resuming (Functional)
เมื่ออุปกรณ์กลับมาทำงานการเตือนสถาณะอุปกรณ์จะกลับมาเหมือนสถาณะเริ่มต้นหรือ false (Device_Fail_Stat = false) เมื่อมีค่าตามเงื่อนไขดังนี้
- Last_Heartbear_Time - Current_Time <= Heartbeat_Time_Threshold

### R4.4: Power Distribution (Functional)

#### R4.4.1: Enabling Every Electronic Power (Except Actuator) (Functional)
เมื่อหุ่นยนต์ไม่ถูกปิดจากสวิตซ์จะทำให้อุปกรณ์ได้รับพลังงานไฟฟ้า (Power_Enable = true) เมื่อมีค่าตามเงื่อนไขดังนี้
- Emer_Sw_Stat == false
- Power_On_Sw_Stat == true
- Act_Sw_Stat == false
- Charger_Sw_Stat == false

#### R4.4.2: Disabling Every Electronic Power (Functional)
เมื่อหุ่นยนต์ถูกปิดจากสวิตซ์จะทำให้อุปกรณ์ไม่ได้รับพลังงานไฟฟ้า(Power_Enable = false) เมื่อมีค่าตามเงื่อนไขดังนี้
- Emer_Sw_Stat == false
- Power_On_Sw_Stat == false
- Act_Sw_Stat == false
- Charger_Sw_Stat == true

#### R4.4.3: Enabling Actuator Power (Functional)
เมื่อหุ่นยนต์ไม่มีสถานะฉุกเฉินหุ่นยนต์หรือเกิดการเปิดสวิตซ์จะมีการเปิดระบบขับเคลื่อน (Act_En = true) เมื่อมีค่าตามเงื่อนไขดังนี้
- Emer_Sw_Stat == false
- Power_On_Sw_Stat == true
- Act_Sw_Stat == true
- Device_Fail_Stat == true
- Charger_Sw_Stat == false

#### R4.4.4: Disabling Actuator Power (Functional)
เมื่อหุ่นยนต์ได้รับสถานะฉุกเฉินหุ่นยนต์หรือเกิดการปิดสวิตซ์จะมีการตัดพลังงานระบบขับเคลื่อน (Act_En = true) เมื่อมีค่าตามเงื่อนไขดังนี้
- Emer_Sw_Stat == true
- Power_On_Sw_Stat == false
- Act_Sw_Stat == false
- Device_Fail_Stat == false
- Charger_Sw_Stat == true

## R5: Resume Behavior (Functional)
เมื่อหุ่นยนต์ไม่มีสถานะฉุกเฉินหุ่นยนต์ หุ่นยนต์จะกลับมาอยู่ในสถานะทำงาน และส่งสัญญาณไปยังระบบประมวลผลเพื่อให้ส่งคำสั่งเพื่อกลับสู่สถานะรอคำสั่ง (Reset_Trig = true) เมื่อมีค่าตามเงื่อนไขดังนี้
- Emer_Sw_Stat == false
- Power_On_Sw_Stat == true
- Act_Sw_Stat == true
- Device_Fail_Stat == false
- Charger_Sw_Stat == false
